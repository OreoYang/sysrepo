module dl {
    namespace urn:tests:dl;
    prefix dl;
    yang-version 1.1;

    container top {
        list item {
            key name;
            leaf name { type string; }
            leaf val { type string; }
            leaf dd { type string; default "d"; }
        }
        leaf-list tag { type string; }
        leaf-list num { type uint32; }
        list ou {
            ordered-by user;
            key name;
            leaf name { type string; }
        }
        container inner {
            leaf a { type string; }
            list x { key name; leaf name { type string; } leaf chk { type string; must "count(../../x) >= 2"; } }
        }
        leaf-list dtag { type string; default "d1"; }
        list pos { key name; leaf name { type string; }
            leaf pp { type string; must "count(../preceding-sibling::pos) >= 1"; } }
        list grp {
            key name;
            leaf name { type string; }
            list mem { key name; leaf name { type string; } }
            leaf need { type string; must "count(../mem) >= 2"; }
            leaf xr { type string; must "count(../../grp/mem) >= 3"; }
            leaf want { type string; }
            leaf other { type string; }
            leaf lv { type string; }
            leaf nx { type string; must "not(../../grp[name = current()/../other]/mem[name = current()/../want])"; }
            leaf nc { type string; must "count(../../grp[name = current()/../other]/mem[name = current()/../want]) = 0"; }
            leaf nf { type string; must "contains(../../grp[name = 'g2']/lv, 'ok')"; }
            leaf mv { type string; must "../../grp[name = 'g2']/lv = 'ok'"; }
            leaf wn { type string; when "not(../../grp[name = current()/../other]/mem[name = current()/../want])"; }
            container pc { leaf np { type string; must "count(../../mem[name = 'x']/../../grp[name = current()/../../other]/mem[name = current()/../../want]) = 0"; } }
        }
        list tpl {
            key name;
            leaf name { type string; }
            list comp { key name; leaf name { type string; } leaf cls { type string; } }
            list ifc {
                key name;
                leaf name { type string; }
                leaf hw { type string; must "../../comp[name = current()]/cls = 'ok'"; }
            }
        }
        list kr {
            key k;
            leaf k { type leafref { path "../../item/name"; } }
        }
        list wr {
            key name;
            leaf name { type string; }
            leaf wref { type leafref { path "../../r/w-on"; } }
        }
        choice wc {
            case wcase {
                when "item[name = 'gate']";
                leaf wc-v { type string; }
            }
            case oc { leaf oc-v { type string; } }
        }
        leaf wcr { type leafref { path "../wc-v"; } }
        list r {
            key name;
            leaf name { type string; }
            leaf sel { type string; }
            leaf lref { type leafref { path "../../item/name"; } }
            leaf tref { type leafref { path "../../tag"; } }
            leaf uref {
                type union {
                    type leafref { path "../../item/name"; }
                    type enumeration { enum none; }
                }
            }
            leaf-list lrefs { type leafref { path "../../item/name"; } }
            leaf dref { type leafref { path "../../item[name = current()/../sel]/val"; } }
            leaf m-exist { type string; must "../../item[name = current()/../sel]"; }
            leaf m-val { type string; must "../../item[name = current()/../sel]/val = 'good'"; }
            leaf m-count { type string; must "count(../../item) >= 2"; }
            leaf m-sum { type string; must "sum(../../num) >= 5"; }
            leaf m-first { type string; must "contains(../../item/val, 'k')"; }
            leaf m-ou1 { type string; must "../../ou[1]/name = 'first'"; }
            leaf m-oul { type string; must "../../ou[last()]/name = 'tail'"; }
            leaf m-dd { type string; must "../../item[name = 'i1']/dd = 'z'"; }
            leaf m-np { type string; must "/dl:c-np/dl:l"; }
            leaf m-desc { type string; must "count(../../inner//dl:name) >= 2"; }
            leaf lrf { type leafref { path "../../item/name"; require-instance false; } }
            leaf m-der { type string; must "deref(../lrf)/../val = 'good'"; }
            leaf m-dflt { type string; must "../../dtag = 'x'"; }
            leaf m-fs { type string; must "count(../following-sibling::r) >= 1"; }
            leaf m-ttag { type string; must "count(../../tag[. = 't1']) = 1"; }
            leaf m-alln { type string; must "count(/dl:top/*) >= 7"; }
            leaf m-anc { type string; must "contains(string(../../inner), 'x1')"; }
            leaf m-anc2 { type string; must "count(../../inner/*) >= 3"; }
            leaf m-anc3 { type string; must "not(contains(string(../../inner), 'bad'))"; }
            leaf m-cap { type string; must "count(/dl:top/dl:item) <= 3"; }
            leaf sw { type string; }
            leaf dep { type string; when "../sw = 'on'"; }
            leaf m-dep { type string; must "../dep"; }
            leaf w-on { type string; when "../../item[name = 'gate']"; }
            leaf dw { type string; default "d"; when "../w-on"; }
        }
    }

    container c-mn { presence "p"; leaf keep { type string; } list mn { min-elements 2; key name; leaf name { type string; } } }
    container c-mt { presence "p"; leaf keep { type string; } leaf-list mt { min-elements 1; type string; } }
    container c-mp { presence "p"; leaf m { type string; mandatory true; } list l { key name; leaf name { type string; } } }
    container c-mc {
        presence "p";
        leaf keep { type string; }
        choice k {
            mandatory true;
            case ca { list la { key name; leaf name { type string; } } }
            case cb { leaf-list lb { type string; } }
        }
    }
    container c-dc {
        leaf keep { type string; }
        choice mode {
            default auto;
            case auto { leaf auto { type string; default "on"; } }
            case manual { list rule { key id; leaf id { type uint32; } } }
        }
    }
    container c-pc { presence "p"; list l { key name; leaf name { type string; } } }
    container c-np { list l { key name; leaf name { type string; } } }
    container c-vk {
        list vk {
            key name;
            leaf name { type string; }
            leaf grp { type string; must "count(../../vk[grp = current()]) >= 2"; }
        }
    }
    container c-neg {
        list un { key name; unique u; max-elements 3; leaf name { type string; } leaf u { type string; } }
        leaf-list mx { max-elements 3; type string; }
    }
    container lone { list li { key name; leaf name { type string; } } }
    container st {
        config false;
        list s { key name; leaf name { type string; } leaf sref { type leafref { path "/dl:top/dl:item/dl:name"; } } }
    }
identity cap-base;
identity cap-download { base cap-base; }
identity cap-sub { base cap-download; }
identity cap-other { base cap-base; }
identity fmt-base;
identity fmt-ssh { base fmt-base; }
identity fmt-other { base fmt-base; }

container pr {
    list shaper { key name; leaf name { type string; } leaf single { type string; } leaf two { type string; } }
    list qprof {
        key name;
        leaf name { type string; }
        container queues {
            list queue {
                key name;
                leaf name { type string; }
                leaf dual { type string; }
                leaf shaper-name {
                    type leafref { path "/dl:pr/dl:shaper/dl:name"; }
                    must "(not(boolean(current()/../dual)) and boolean(/dl:pr/dl:shaper[dl:name=current()]/dl:single)) or (boolean(current()/../dual) and boolean(/dl:pr/dl:shaper[dl:name=current()]/dl:two))";
                }
            }
        }
    }
    list bq {
        key name;
        leaf name { type string; }
        leaf sref { type leafref { path "/dl:pr/dl:shaper/dl:name"; } }
        leaf burst { type string; when "boolean(/dl:pr/dl:shaper[dl:name=current()/../sref]/dl:single)"; }
    }
    list tmpl { key name; leaf name { type string; } list ifc { key name; leaf name { type string; } leaf v4 { type string; } leaf v6 { type string; } } }
    list onu {
        key name;
        leaf name { type string; }
        leaf tref { type string; }
        list term {
            key name;
            leaf name { type string; }
            leaf peer { type leafref { path "../../term/name"; } }
            leaf ipif {
                type string;
                must "boolean(/dl:pr/dl:tmpl[dl:name=current()/ancestor::dl:onu/dl:tref]/dl:ifc[dl:name=current()]/dl:v4) or boolean(/dl:pr/dl:tmpl[dl:name=current()/ancestor::dl:onu/dl:tref]/dl:ifc[dl:name=current()]/dl:v6)";
            }
        }
    }
    list comp {
        key name;
        leaf name { type string; }
        container revs {
            leaf cap { type string; }
            leaf dcap { type identityref { base cap-base; } }
            list rev {
                key name;
                leaf name { type string; }
                leaf state { type string; }
                leaf alias { type string; when "boolean(../../cap='alias')"; }
                leaf act { type string; when "boolean(../../cap='act') and (../state='available' or ../state='in-use')"; }
                leaf fin { type string; when "derived-from(../../dcap, 'dl:cap-download') and ../state != 'downloading'"; }
            }
            leaf download { type string; when "derived-from(../dcap, 'dl:cap-download') and count(../rev[state='downloading'])=0"; }
        }
    }
    list tp {
        key name;
        leaf name { type string; }
        container tcs {
            must "not(boolean(tc)) or tc[not(../tc/position > position)]/position <= count(current()/tc)";
            list tc { key position; leaf position { type uint32; } leaf duration { type string; } }
            leaf rb { type string; when "(count(../tc) > 1) and ../tc[position=count(../tc)]/duration != 'continuous'"; }
        }
    }
    list tsb { key name; leaf name { type string; } list pk { key name; leaf name { type string; } leaf fmt { type identityref { base fmt-base; } } } }
    list usr {
        key name;
        leaf name { type string; }
        leaf ref {
            type leafref { path "/dl:pr/dl:tsb/dl:name"; }
            must "not(deref(.)/../dl:pk/dl:fmt[not(derived-from-or-self(., 'dl:fmt-ssh'))])";
        }
    }
}
container gp {
    list g {
        key name;
        leaf name { type string; }
        leaf b { type string; }
        leaf d { type string; }
        leaf s { type string; }
        leaf peer { type string; }
        list c { key name; leaf name { type string; } }
        list lst { key name; leaf name { type string; } leaf tag { type string; } leaf kind { type identityref { base cap-base; } } }
        leaf la1 { type string; must "not(../b)"; }
        leaf la2 { type string; must "count(../c) >= 1"; }
        leaf la3 { type string; must "string-length(../s) > 2"; }
        leaf la4 { type string; must "string-length(.) > 2"; }
        leaf la5 { type string; must "../d"; }
        leaf la6 { type string; must ". = 'ok'"; }
        leaf lr1 { type leafref { path "../d"; } }
        leaf lr2 { type leafref { path "../lst/tag"; } }
        leaf ls1 { type string; must "count(../lst[tag = 'x']) >= 1"; }
        leaf wl1 { type string; when "../lst[tag = 'on']"; }
        leaf wl2 { type string; when "not(../b)"; }
        leaf bd { type string; must "count(../../g[name = current()/../peer]/lst) >= 1"; }
        leaf bq { type string; must "not(boolean(../b)) and boolean(/dl:gp/dl:u[dl:name = current()]/dl:tag)"; }
        leaf cq { type string; must "count(/dl:gp/dl:u[dl:tag = current()]) < 2"; }
        leaf gk { type identityref { base cap-base; } }
        leaf pp { type string; }
        leaf pk { type string; must "derived-from-or-self(/dl:gp/dl:g[dl:name = current()]/dl:gk, 'dl:cap-sub') and /dl:gp/dl:g[dl:name = current()]/dl:d = ../d and (not(../pp) or (current() != ../pp))"; }
        leaf pc { type string; must "derived-from-or-self(/dl:gp/dl:g[dl:name = current()]/dl:gk, 'dl:cap-sub') and not(/dl:gp/dl:uq[dl:name = current()])"; }
        leaf ld { type string; must "derived-from-or-self(../lst[name = current()]/kind, 'dl:cap-sub')"; }
    }
    list u { key name; leaf name { type string; } leaf tag { type string; } leaf r { type leafref { path "../../u/tag"; } } }
    list uq { key name; unique tag; leaf name { type string; } leaf tag { type string; } }
    leaf wu { type string; when "/dl:gp/dl:u/dl:tag = 'on'"; }
    leaf wb { type string; when "not(/dl:gp/dl:u[dl:name = 'z'])"; }
}
container gs {
    presence "x";
    list mcl { key name; leaf name { type string; } choice ch { mandatory true; case a { leaf ca { type string; } } case b { leaf cb { type string; } } } }
    list mml { key name; leaf name { type string; } leaf mand { type string; mandatory true; } }
    list mxl { key name; max-elements 2; leaf name { type string; } }
    list mnl { key name; min-elements 2; leaf name { type string; } }
}
}
